module bbf-polt-vomci {
  yang-version 1.1;
  namespace "urn:bbf:yang:bbf-polt-vomci";
  prefix bbf-polt-vomci;

  import bbf-yang-types {
    prefix bbf-yang;
  }
  import bbf-nf-client {
    prefix bbf-nf-client;
  }
  import bbf-nf-server {
    prefix bbf-nf-server;
  }
  import bbf-nf-endpoint-filter {
    prefix bbf-nf-epf;
  }

  organization
    "Broadband Forum <https://www.broadband-forum.org>
     SDN/NFV Work Area";
  contact
    "Comments or questions about this Broadband Forum YANG module
     should be directed to <mailto:help@broadband-forum.org>.

     Editor:      Tim Carey, Nokia

     Editor:      Dechao Zhang, China Mobile

     PS Leader:   Yves Hertoghs, VMWare

     WA Director: George Dobrowski, Morris Creek Consulting

     WA Director: Bruno Cornaglia, Vodafone";
  description
    "This module contains a collection of YANG definitions needed to
     for a physical OLTs implementation of the vOMCI functionality
     as described in TR-451.

     Copyright (c) 2019-2020, Broadband Forum

     Redistribution and use in source and binary forms, with or
     without modification, are permitted provided that the following
     conditions are met:

     1. Redistributions of source code must retain the above copyright
        notice, this list of conditions and the following disclaimer.

     2. Redistributions in binary form must reproduce the above
        copyright notice, this list of conditions and the following
        disclaimer in the documentation and/or other materials
        provided with the distribution.

     3. Neither the name of the copyright holder nor the names of its
        contributors may be used to endorse or promote products
        derived from this software without specific prior written
        permission.

     THIS SOFTWARE IS PROVIDED BY THE COPYRIGHT HOLDERS AND
     CONTRIBUTORS \"AS IS\" AND ANY EXPRESS OR IMPLIED WARRANTIES,
     INCLUDING, BUT NOT LIMITED TO, THE IMPLIED WARRANTIES OF
     MERCHANTABILITY AND FITNESS FOR A PARTICULAR PURPOSE ARE
     DISCLAIMED. IN NO EVENT SHALL THE COPYRIGHT HOLDER OR
     CONTRIBUTORS BE LIABLE FOR ANY DIRECT, INDIRECT, INCIDENTAL,
     SPECIAL, EXEMPLARY, OR CONSEQUENTIAL DAMAGES (INCLUDING, BUT
     NOT LIMITED TO, PROCUREMENT OF SUBSTITUTE GOODS OR SERVICES;
     LOSS OF USE, DATA, OR PROFITS; OR BUSINESS INTERRUPTION) HOWEVER
     CAUSED AND ON ANY THEORY OF LIABILITY, WHETHER IN CONTRACT,
     STRICT LIABILITY, OR TORT (INCLUDING NEGLIGENCE OR OTHERWISE)
     ARISING IN ANY WAY OUT OF THE USE OF THIS SOFTWARE, EVEN IF
     ADVISED OF THE POSSIBILITY OF SUCH DAMAGE.

     The above license is used as a license under copyright only.
     Please reference the Forum IPR Policy for patent licensing terms
     <https://www.broadband-forum.org/ipr-policy>.

     Any moral rights which are necessary to exercise under the above
     license grant are also deemed granted under this license.

     This version of this YANG module is part of TR-451; see
     the TR itself for full legal notices.";

  revision 2019-10-09 {
    description
      "Initial revision.";
    reference
      "TR-451: Section 5.2 OLT Description
               Section 5.5 vOMCI Function to OLT Interface";
  }

  // Features

  feature nf-client-supported {
    description
      "Indicates that client connectivity to network function's
       endpoints is supported.";
  }

  feature nf-server-supported {
    description
      "Indicates that server connectivity for network function's
       endpoints is supported.";
  }

  container remote-nf-settings {
    presence "Enables access to remote network functions";
    description
      "Container for remote network function settings";
    container nf-client {
      if-feature "bbf-polt-vomci:nf-client-supported";
      description
        "Container for client network function settings";
      leaf enabled {
        type boolean;
        default "true";
        description
          "Administratively enable the use of the client connectivity
           capability to the network function.";
      }
      container client-parameters {
        uses bbf-nf-client:nf-endpoint-grouping;
        description
          "Container for network function client configuration.";
      }
      container nf-endpoint-filter {
        description
          "The network function endpoint filter.";
        list rule {
          key "name";
          // min-elements 1;
          description
            "A rule contains a classification of resources that
             match a criteria. The result is an endpoint name.
             The definition is: first match, then stop searching
             for matches with other rules, obtain the resulting
             endpoint specified in this rule.";
          leaf name {
            type bbf-yang:string-ascii64;
            description
              "The rule name.";
          }
          leaf priority {
            type uint16 {
              range "1..max";
            }
            mandatory true;
            description
              "This field indicates the priority for applying the
               match criteria of this rule against the priority of
               match criteria of other rules in this filter.

               The higher the value, the lower the priority, i.e.
               priority 1 is the highest priority.";
          }
          container flexible-match {
            uses bbf-nf-epf:onu-criteria-grouping;
            description
              "This container provides a generic framework to
               specify match criteria for endpoint filters. Specific
               match criteria shall be provided using augments in
               a context dependent way, e.g. match criteria can be
               augmented for ONUs, or in another context match
               criteria can be augmented for another resource.";
          }
          leaf resulting-endpoint {
            type leafref {
              path "/remote-nf-settings/nf-client/client-parameters/"
                 + "nf-initiate/remote-endpoints/name";
            }
            description
              "The resulting endpoint name.";
          }
        }
        // rules
      }
      //nf-endpoint-filter
    }
    //nf-client
    container nf-server {
      if-feature "bbf-polt-vomci:nf-server-supported";
      description
        "Container for server network function settings";
      leaf enabled {
        type boolean;
        default "true";
        description
          "Administratively enable the use of the server connectivity
           capability for connecting network function.";
      }
      container server-parameters {
        uses bbf-nf-server:nf-server-grouping;
        description
          "Container for network function server configuration.";
      }
      container nf-endpoint-filter {
        description
          "The network function endpoint filter.";
        list rule {
          key "name";
          // min-elements 1;
          description
            "A rule contains a classification of resources that
             match a criteria. The result is an endpoint name.
             The definition is: first match, then stop searching
             for matches with other rules, obtain the resulting
             endpoint specified in this rule.";
          leaf name {
            type bbf-yang:string-ascii64;
            description
              "The rule name.";
          }
          leaf priority {
            type uint16 {
              range "1..max";
            }
            mandatory true;
            description
              "This field indicates the priority for applying the
               match criteria of this rule against the priority of
               match criteria of other rules in this filter.

               The higher the value, the lower the priority, i.e.
               priority 1 is the highest priority.";
          }
          container flexible-match {
            uses bbf-nf-epf:onu-criteria-grouping;
            description
              "This container provides a generic framework to
               specify match criteria for endpoint filters. Specific
               match criteria shall be provided using augments in
               a context dependent way, e.g. match criteria can be
               augmented for ONUs, or in another context match
               criteria can be augmented for another resource.";
          }
          leaf resulting-endpoint {
            type leafref {
              path "/remote-nf-settings/nf-server/server-parameters/"
                 + "listen/remote-endpoints/name";
              require-instance "false";
            }
            description
              "The resulting endpoint name.";
          }
        }
        // rules
      }
      //nf-endpoint-filter
    }
    //nf-server
  }

  //remote-nf-settings
}
