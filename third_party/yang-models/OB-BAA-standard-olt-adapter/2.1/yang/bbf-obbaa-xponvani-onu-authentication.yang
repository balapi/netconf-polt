module bbf-obbaa-xponvani-onu-authentication {
  yang-version 1.1;
  namespace "urn:bbf:yang:obbaa:xponvani-onu-authentication";
  prefix baa-xponvani-onu-auth;

  import ietf-interfaces {
    prefix if;
  }

  import bbf-xponvani {
    prefix bbf-xponvani;
  }

  import bbf-yang-types {
    prefix bbf-yang;
  }

  import bbf-obbaa-xpon-onu-types {
    prefix baa-xpon-onu-types;
  }
  
  organization
    "Broadband Forum <https://www.broadband-forum.org>
     Fiber Access Networks Work Area";
  contact
     "Comments or questions about this Broadband Forum YANG module
     should be directed to <mailto:obbaa-leaders@broadband-forum.org>.
    ";

  description
    "This module contains a collection of YANG definitions for
     supporting the Broadband Forum requirements on management of
     ITU-T Passive Optical Network (PON) interfaces as defined in
     ITU-T G.984.x, G.987.x, ITU-T G.989.x and ITU-T G.9807.x. As
     such, this module is specific to access network equipment (e.g.,
     BBF-specified Access Nodes and FTTdp DPUs).

     Specifically, this module defines state data and notifications
     related to the authentication of Optical Network Units (ONUs) 
     and how to determine whether an ONU is to be managed by an OMCI
     function embedded in the OLT (eOMCI) or by a virtualized OMCI 
     function (vOMCI).

     Copyright 2021 Broadband Forum
     
     Licensed under the Apache License, Version 2.0 (the \"License\");
     you may not use this file except in compliance with the License.
     You may obtain a copy of the License at
     
     http://www.apache.org/licenses/LICENSE-2.0
     Unless required by applicable law or agreed to in writing, software
     distributed under the License is distributed on an \"AS IS\" BASIS,
     WITHOUT WARRANTIES OR CONDITIONS OF ANY KIND, either express or implied.
     See the License for the specific language governing permissions and
     limitations under the License.";

  revision 2021-11-10 {
    description
       "Initial revision.";
    reference
       "broadband_forum";
  }


//
// Augments 
//

  augment "/if:interfaces/if:interface/bbf-xponvani:v-ani" {
    description
      "Configuration data for an xPON virtual Access Network 
       Interface (vANI) to support authenticating an Optical 
       Network Unit (ONU) and determining whether the ONU should 
       be managed via an OMCI function (eOMCI) embedded in the 
       Optical Line Termination (OLT) or via a virtualized OMCI 
       function (vOMCI).";
    leaf onu-name {
      type bbf-yang:string-ascii64;
      description
        "The name of the Optical Network Unit (ONU) device 
         corresponding to this virtual Access Network 
         Interface (vANI). This 'onu-name' could be used as
         means to help correlating ONU authentication activity 
         in the OLT and the Management plane. For instance it 
         could be used as a key to a managed ONU in the device 
         list in the device aggregation function of the Management 
         Plane.";
      reference
        "WT-489";
    }

    leaf expected-loid {
      type string {
        length "1..24";
      }
      description
        "The LOID value that the Optical Line Termination (OLT) 
         expects to retrieve from the Optical Network Unit (ONU).";
      reference
        "ITU-T G.988 Clause 9.1.1 
         WT-489";
    }

    leaf planned-onu-management-mode {
      type identityref {
        base baa-xpon-onu-types:onu-management-config-base;
      }
      description
        "The planed management mode of the Optical Network Unit 
         (ONU) corresponding to this virtual Access Network 
         Interface (vANI).";
      reference
        "WT-489";
    }
  }

  augment "/if:interfaces-state/if:interface/bbf-xponvani:v-ani/"
        + "bbf-xponvani:onu-present-on-this-olt"{
    description
      "Adds to the virtual Access Network Interface (vANI) state 
       data information related to Optical Network Unit (ONU) 
       authentication when the corresponding ONU is present on 
       a channel termination.";
    leaf detected-loid {
      type string {
        length "1..24";
      }
      description
        "The LOID value which the Optical Line Termination (OLT)
         could fetched from the Optical Network Unit (ONU). 
         This leaf is not present if the ONU has not provided 
         any LOID to the OLT. LOID may be useful in identifying 
         a particular ONU installed at a particular location.";
      reference
        "ITU-T G.988 Clause 9.1.1 
         WT-489";
    }
    leaf determined-onu-management-mode {
      type identityref {
        base baa-xpon-onu-types:onu-management-state-base;
      }
      description
        "This YANG leaf may only be present when the corresponding 
         Optical Network Unit (ONU) is present on a channel 
         termination and has been successfully authenticated. 
         It provides the ONU management mode as best determined  
         by the Optical Line Termination (OLT), ideally  
         discriminating between eOMCI and vOMCI."; 
      reference
        "WT-489";
    }
  }

}
