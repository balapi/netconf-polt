module bbf-qos-policies-sub-interface-rewrite {
  yang-version 1.1;
  namespace "urn:bbf:yang:bbf-qos-policies-sub-interface-rewrite";
  prefix bbf-qos-pol-subif-rw;

  import ietf-interfaces {
    prefix if;
  }
  import bbf-qos-classifiers {
    prefix bbf-qos-cls;
  }
  import bbf-frame-classification {
    prefix bbf-classif;
  }
  import bbf-sub-interfaces {
    prefix bbf-subif;
  }

  organization
    "Broadband Forum <https://www.broadband-forum.org>
     Common YANG Work Area";
  contact
    "Comments or questions about this Broadband Forum YANG module
     should be directed to <mailto:help@broadband-forum.org>.

     Editor:      Nick Hancock, ADTRAN

     Editor:      Ludwig Pauwels, Nokia

     PS Leader:   Joey Boyd, ADTRAN

     PS Leader:   Sowrirajan Padmanabhan, Nokia

     WA Director: Joey Boyd, ADTRAN

     WA Director: Sven Ooghe, Nokia";
  description
    "This module contains a collection of YANG definitions for
     supporting the Broadband Forum requirements on the management of
     Quality of Service (QoS) as applicable to access network
     equipment. As such, this module is specific to access network
     equipment (e.g., BBF-specified Access Nodes and FTTdp DPUs).

     Specifically, this module contains augments to sub-interfaces to
     support policies applied to frames.

     Copyright (c) 2017-2021, Broadband Forum

     Redistribution and use in source and binary forms, with or
     without modification, are permitted provided that the following
     conditions are met:

     1. Redistributions of source code must retain the above copyright
        notice, this list of conditions and the following disclaimer.

     2. Redistributions in binary form must reproduce the above
        copyright notice, this list of conditions and the following
        disclaimer in the documentation and/or other materials
        provided with the distribution.

     3. Neither the name of the copyright holder nor the names of its
        contributors may be used to endorse or promote products
        derived from this software without specific prior written
        permission.

     THIS SOFTWARE IS PROVIDED BY THE COPYRIGHT HOLDERS AND
     CONTRIBUTORS \"AS IS\" AND ANY EXPRESS OR IMPLIED WARRANTIES,
     INCLUDING, BUT NOT LIMITED TO, THE IMPLIED WARRANTIES OF
     MERCHANTABILITY AND FITNESS FOR A PARTICULAR PURPOSE ARE
     DISCLAIMED. IN NO EVENT SHALL THE COPYRIGHT HOLDER OR
     CONTRIBUTORS BE LIABLE FOR ANY DIRECT, INDIRECT, INCIDENTAL,
     SPECIAL, EXEMPLARY, OR CONSEQUENTIAL DAMAGES (INCLUDING, BUT
     NOT LIMITED TO, PROCUREMENT OF SUBSTITUTE GOODS OR SERVICES;
     LOSS OF USE, DATA, OR PROFITS; OR BUSINESS INTERRUPTION) HOWEVER
     CAUSED AND ON ANY THEORY OF LIABILITY, WHETHER IN CONTRACT,
     STRICT LIABILITY, OR TORT (INCLUDING NEGLIGENCE OR OTHERWISE)
     ARISING IN ANY WAY OUT OF THE USE OF THIS SOFTWARE, EVEN IF
     ADVISED OF THE POSSIBILITY OF SUCH DAMAGE.

     The above license is used as a license under copyright only.
     Please reference the Forum IPR Policy for patent licensing terms
     <https://www.broadband-forum.org/ipr-policy>.

     Any moral rights which are necessary to exercise under the above
     license grant are also deemed granted under this license.

     This version of this YANG module is part of TR-383a4; see
     the TR itself for full legal notices.";

  revision 2021-06-02 {
    description
      "Amendment 4.
       * Approval Date:    2021-06-02.
       * Publication Date: 2021-06-02.";
    reference
      "TR-383a4: Common YANG Modules
                 <https://www.broadband-forum.org/technical/download/
                          TR-383_Amendment-4.pdf>";
  }
  revision 2020-10-13 {
    description
      "Amendment 3.
       * Approval Date:    2020-10-13.
       * Publication Date: 2020-10-13.";
    reference
      "TR-383a3: Common YANG Modules
                 <https://www.broadband-forum.org/technical/download/
                          TR-383_Amendment-3.pdf>";
  }

  augment
    "/if:interfaces/if:interface/bbf-subif:frame-processing/"
  + "bbf-subif:inline-frame-processing/bbf-subif:inline-frame-"
  + "processing/bbf-subif:ingress-rule/bbf-subif:rule/"
  + "bbf-subif:ingress-rewrite" {
    description
      "Augments the VLAN sub-interface with ingress-rewrite actions.";
    list copy-from-tags-to-marking-list {
      key "tag-index";
      description
        "An input VLAN tag from which p-bits and/or DEI field content
         will be preserved.";
      leaf tag-index {
        type bbf-classif:tag-index;
        description
          "Specifies from which input VLAN tag fields MUST be copied
           to the frame's marking-list.";
      }
      leaf pbit-marking-index {
        type union {
          type enumeration {
            enum not-preserved {
              description
                "The p-bits are not preserved.";
            }
          }
          type bbf-qos-cls:qos-pbit-marking-index;
        }
        default "not-preserved";
        description
          "Specifies the index of the frame's pbit marking list to
           which the p-bits shall be copied.";
      }
      leaf dei-marking-index {
        type union {
          type enumeration {
            enum not-preserved {
              description
                "The DEI bit is not preserved.";
            }
          }
          type bbf-qos-cls:qos-pbit-marking-index;
        }
        default "not-preserved";
        description
          "Specifies the index of the frame's dei marking list to
           which the DEI bit shall be copied.";
      }
    }
  }
}
