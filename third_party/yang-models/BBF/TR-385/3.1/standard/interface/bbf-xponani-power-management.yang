module bbf-xponani-power-management {
  yang-version 1.1;
  namespace "urn:bbf:yang:bbf-xponani-power-management";
  prefix bbf-xponani-pwr;

  import bbf-yang-types {
    prefix bbf-yang;
  }
  import ietf-interfaces {
    prefix if;
  }
  import bbf-xponani {
    prefix bbf-xponani;
  }
  import bbf-xpon-power-management {
    prefix bbf-xpon-pwr;
  }

  organization
    "Broadband Forum <https://www.broadband-forum.org>
     Fiber Access Networks Work Area";
  contact
    "Comments or questions about this Broadband Forum YANG module
     should be directed to <mailto:info@broadband-forum.org>.

     Editor:      Joey Boyd, ADTRAN

     Editor:      Igor Ternovsky, Broadcom

     Editor:      Robert Peschi, Nokia

     WA Director: Marta Seda, Calix

     WA Director: Samuel Chen, Broadcom";
  description
    "This module contains a collection of YANG definitions for 
     supporting the Broadband Forum requirements on management of 
     ITU-T Passive Optical Network (PON) interfaces as defined in 
     ITU-T G.984.x, G.987.x, ITU-T G.989.x and ITU-T G.9807.x. As 
     such, this module is specific to access network equipment (e.g., 
     BBF-specified Access Nodes and FTTdp DPUs).

     Specifically, this module defines Optical Network Unit (ONU) 
     power management at the Access Network Interface (ANI).

     Copyright (c) 2018-2020, Broadband Forum

     Redistribution and use in source and binary forms, with or
     without modification, are permitted provided that the following
     conditions are met:

     1. Redistributions of source code must retain the above copyright
        notice, this list of conditions and the following disclaimer.

     2. Redistributions in binary form must reproduce the above
        copyright notice, this list of conditions and the following
        disclaimer in the documentation and/or other materials
        provided with the distribution.

     3. Neither the name of the copyright holder nor the names of its
        contributors may be used to endorse or promote products
        derived from this software without specific prior written
        permission.

     THIS SOFTWARE IS PROVIDED BY THE COPYRIGHT HOLDERS AND
     CONTRIBUTORS \"AS IS\" AND ANY EXPRESS OR IMPLIED WARRANTIES,
     INCLUDING, BUT NOT LIMITED TO, THE IMPLIED WARRANTIES OF
     MERCHANTABILITY AND FITNESS FOR A PARTICULAR PURPOSE ARE
     DISCLAIMED. IN NO EVENT SHALL THE COPYRIGHT HOLDER OR
     CONTRIBUTORS BE LIABLE FOR ANY DIRECT, INDIRECT, INCIDENTAL,
     SPECIAL, EXEMPLARY, OR CONSEQUENTIAL DAMAGES (INCLUDING, BUT
     NOT LIMITED TO, PROCUREMENT OF SUBSTITUTE GOODS OR SERVICES;
     LOSS OF USE, DATA, OR PROFITS; OR BUSINESS INTERRUPTION) HOWEVER
     CAUSED AND ON ANY THEORY OF LIABILITY, WHETHER IN CONTRACT,
     STRICT LIABILITY, OR TORT (INCLUDING NEGLIGENCE OR OTHERWISE)
     ARISING IN ANY WAY OUT OF THE USE OF THIS SOFTWARE, EVEN IF
     ADVISED OF THE POSSIBILITY OF SUCH DAMAGE.

     The above license is used as a license under copyright only.
     Please reference the Forum IPR Policy for patent licensing terms
     <https://www.broadband-forum.org/ipr-policy>.

     Any moral rights which are necessary to exercise under the above
     license grant are also deemed granted under this license.

     This version of this YANG module is part of TR-385i2; see
     the TR itself for full legal notices.";

  revision 2020-05-11 {
    description
      "Issue 2 Straw Ballot.
       * Approval Date:    TBD.
       * Publication Date: TBD.";
    reference
      "TR-385i2: ITU-T PON YANG Modules
               <https://www.broadband-forum.org/technical/download/
                        TR-385_Issue-2.pdf>";
  }

  grouping ani-power-management-profiles-data {
    description
      "ONU-side configuration data for Optical Network Unit (ONU) 
       power management.";
    list power-management-profile {
      key "name";
      description
        "Optical Network Unit (ONU) power management configuration 
         parameters.";
      reference
        "ITU-T G.988 clause 9.1.14";
      leaf name {
        type bbf-yang:string-ascii64;
        description
          "Power management profile name.";
      }
      leaf-list mode {
        type identityref {
          base bbf-xpon-pwr:power-mode-base;
        }
        min-elements 1;
        description
          "List of enabled power reduction management modes.";
      }
      leaf irxoff {
        type uint32;
        units "125 us PHY frames";
        description
          "Irxoff the maximum time the Optical Line Termination (OLT) 
           can afford to wait from the moment it decides to wake up an
           Optical Network Unit (ONU) in the low-power state of the 
           watchful sleep mode until the ONU is fully operational, 
           specified as a count of 125 us PHY frames.";
        reference
          "ITU-T G.988 clause 9.1.14";
      }
      leaf iaware {
        type uint32;
        units "125 us PHY frames";
        description
          "The Iaware attribute specifies the time the Optical Network
           Unit (ONU) spends in its aware state, as a count of 125 us 
           PHY frames, before it re-enters asleep or listen states. 
           Local or remote events may independently cause the ONU to 
           enter an active state rather than returning to a sleep 
           state.";
        reference
          "ITU-T G.988 clause 9.1.14";
      }
      leaf ihold {
        type uint16;
        units "125 us PHY frames";
        description
          "The Ihold attribute specifies the minimum time during which
           the Optical Network Unit (ONU) remains in the active held 
           state, as a count of 125 us PHY frames.";
        reference
          "ITU-T G.988 clause 9.1.14";
      }
      leaf idoze {
        type uint32;
        units "125 us PHY frames";
        description
          "Maximum sleep interval in doze mode, specified in units of
           125 us PHY frames.

           This parameter must be set to a value greater than 0 if
           Optical Network Unit (ONU) supports doze mode.";
        reference
          "ITU-T G.988 clause 9.1.14";
      }
      leaf icyclic-sleep {
        type uint32;
        units "125 us PHY frames";
        default "0";
        description
          "Maximum sleep interval in cyclic-sleep mode, specified in
           units of 125 us PHY frames.

           Local or remote events may cause the Optical Network Unit 
           (ONU) to leave this state. This parameter must be set to a 
           value greater than 0 if ONU supports cyclic sleep mode.";
        reference
          "ITU-T G.988 clause 9.1.14";
      }
    }
  }

  container xponani-power-management-profiles {
    if-feature "bbf-xpon-pwr:xpon-power-management";
    uses ani-power-management-profiles-data;
    description
      "Power management profiles.";
  }

  augment "/if:interfaces/if:interface/bbf-xponani:ani" {
    if-feature "bbf-xpon-pwr:xpon-power-management";
    description
      "Optical Network Unit (ONU) power management configuration";
    container power-management {
      presence
        "The presence of this container indicates that Optical Network
         Unit (ONU) power management is enabled.";
      description
        "Power management configuration.";
      leaf power-management-profile-ref {
        type leafref {
          path "/xponani-power-management-profiles"
             + "/power-management-profile/name";
        }
        mandatory true;
        description
          "Optical Network Unit (ONU) power management profile 
           reference.";
      }
    }
  }

  augment "/if:interfaces-state/if:interface/bbf-xponani:ani" {
    if-feature "bbf-xpon-pwr:xpon-power-management";
    description
      "Optical Network Unit (ONU) power management status 
       information";
    container power-management {
      description
        "Optical Network Unit (ONU) power management capabilities and 
         status.";
      leaf power-management-state {
        type identityref {
          base bbf-xpon-pwr:power-state-base;
        }
        description
          "Optical Network Unit (ONU) power management state at 
           Optical Line Termination (OLT).";
        reference
          "ITU-T G.9807.1 clause C.16.1
           ITU-T G.989.3 clause 16
           ITU-T G.987.3 clause 16
           ITU-T G.984.3 Annex E.";
      }
      leaf-list capability {
        type identityref {
          base bbf-xpon-pwr:power-mode-base;
        }
        description
          "List of dynamic power management capabilities supported
           by the Optical Network Unit (ONU).";
        reference
          "ITU-T G.988.x clause 9.1.14.";
      }
      leaf itransinit {
        type uint16;
        units "125 us PHY frames";
        description
          "Optical Network Unit (ONU) vendor's statement of the 
           complete transceiver initialization time: the time required
           for the ONU to regain full functionality when leaving the 
           asleep state (i.e., turning on both the receiver and the 
           transmitter and acquiring synchronization to the downstream
           flow), measured in units of 125 us PHY frames. The value 
           zero indicates that the sleeping ONU can respond to a 
           bandwidth grant without delay.";
        reference
          "ITU-T G.988 clause 9.1.14";
      }
      leaf itxinit {
        type uint16;
        units "125 us PHY frames";
        description
          "This attribute is the Optical Network Unit (ONU) vendor's 
           statement of the transmitter initialization time: the time 
           required for the ONU to regain full functionality when 
           leaving the listen state (i.e., turning on the 
           transmitter), measured in units of 125 us PHY frames. The 
           value zero indicates that the dozing ONU can respond to a 
           bandwidth grant without delay.";
        reference
          "ITU-T G.988 clause 9.1.14";
      }
    }
  }
}
