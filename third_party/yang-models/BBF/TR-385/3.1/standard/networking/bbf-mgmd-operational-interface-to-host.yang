submodule bbf-mgmd-operational-interface-to-host {
  yang-version 1.1;
  belongs-to bbf-mgmd {
    prefix bbf-mgmd;
  }

  import ietf-yang-types {
    prefix yang;
  }

  organization
    "Broadband Forum <https://www.broadband-forum.org>
     Common YANG Work Area";
  contact
    "Comments or questions about this Broadband Forum YANG module
     should be directed to <mailto:help@broadband-forum.org>.

     Editor:      Nick Hancock, ADTRAN

     Editor:      Ludwig Pauwels, Nokia

     PS Leader:   Joey Boyd, ADTRAN

     PS Leader:   Sowrirajan Padmanabhan, Nokia

     WA Director: Joey Boyd, ADTRAN

     WA Director: Sven Ooghe, Nokia";
  description
    "This module contains a collection of YANG definitions for
     supporting the Multicast Group Membership Discovery (MGMD)
     Protocols. In particular, it describes state objects used for
     managing the Internet Group Management Protocol (IGMP) and the
     Multicast Listener Discovery (MLD) protocol on interfaces that
     connect a system to multicast hosts.

     Copyright (c) 2017-2020, Broadband Forum

     Redistribution and use in source and binary forms, with or
     without modification, are permitted provided that the following
     conditions are met:

     1. Redistributions of source code must retain the above copyright
        notice, this list of conditions and the following disclaimer.

     2. Redistributions in binary form must reproduce the above
        copyright notice, this list of conditions and the following
        disclaimer in the documentation and/or other materials
        provided with the distribution.

     3. Neither the name of the copyright holder nor the names of its
        contributors may be used to endorse or promote products
        derived from this software without specific prior written
        permission.

     THIS SOFTWARE IS PROVIDED BY THE COPYRIGHT HOLDERS AND
     CONTRIBUTORS \"AS IS\" AND ANY EXPRESS OR IMPLIED WARRANTIES,
     INCLUDING, BUT NOT LIMITED TO, THE IMPLIED WARRANTIES OF
     MERCHANTABILITY AND FITNESS FOR A PARTICULAR PURPOSE ARE
     DISCLAIMED. IN NO EVENT SHALL THE COPYRIGHT HOLDER OR
     CONTRIBUTORS BE LIABLE FOR ANY DIRECT, INDIRECT, INCIDENTAL,
     SPECIAL, EXEMPLARY, OR CONSEQUENTIAL DAMAGES (INCLUDING, BUT
     NOT LIMITED TO, PROCUREMENT OF SUBSTITUTE GOODS OR SERVICES;
     LOSS OF USE, DATA, OR PROFITS; OR BUSINESS INTERRUPTION) HOWEVER
     CAUSED AND ON ANY THEORY OF LIABILITY, WHETHER IN CONTRACT,
     STRICT LIABILITY, OR TORT (INCLUDING NEGLIGENCE OR OTHERWISE)
     ARISING IN ANY WAY OUT OF THE USE OF THIS SOFTWARE, EVEN IF
     ADVISED OF THE POSSIBILITY OF SUCH DAMAGE.

     The above license is used as a license under copyright only.
     Please reference the Forum IPR Policy for patent licensing terms
     <https://www.broadband-forum.org/ipr-policy>.

     Any moral rights which are necessary to exercise under the above
     license grant are also deemed granted under this license.

     This version of this YANG module is part of TR-383a3; see
     the TR itself for full legal notices.";

  revision 2020-05-11 {
    description
      "Amendment 3 Straw Ballot
       * Approval Date:    TBD.
       * Publication Date: TBD.";
    reference
      "TR-383a3: Common YANG Modules
                 <https://www.broadband-forum.org/technical/download/
                          TR-383_Amendment-3.pdf>";
  }
  revision 2018-07-13 {
    description
      "Amendment 1.
       * Approval Date:    2018-06-04.
       * Publication Date: see revision date above.";
    reference
      "TR-383: Common YANG Modules
               <https://www.broadband-forum.org/technical/download/
                        TR-383_Amendment-1.pdf>";
  }

  grouping mgmd-interface-to-hosts-receive-state {
    description
      "Grouping of objects used for monitoring the Internet Group
       Management Protocol (IGMP) and the Multicast Listener Discovery
       (MLD) protocol on interfaces that connect a system to a
       multicast host.";
    leaf in-successful-join-requests {
      type yang:counter32;
      description
        "Counts the total number of successful join requests received
         from hosts connected to the interface. This includes new
         joins (which make a new connection) and re-joins (which
         already have a connection).

         For MGMD version 2 it counts the number of Membership Report
         messages that resulted in a successful join.

         MGMD version 3 defines a Membership Report message to contain
         multiple group records. Within a group record there is a
         parameter 'multicast address' and a list of 'source
         addresses'. A tree is managed per (multicast address, source
         address) pair. Hence a join is a request that requests
         associating the interface to a tree. In case one Membership
         Report message results in requests for associating the
         interface to N trees, then this corresponds to N joins. For
         MGMD version 3 the counter result in-successful-join-requests
         counts the number of joins that in successfully associating
         the interface to a tree.";
      reference
        "TR-101 - R-217, per DSL port, per multicast VLAN, item 1";
    }
    leaf in-unsuccessful-join-requests {
      type yang:counter32;
      description
        "Counts the total number of unsuccessful new join requests
         from hosts connected to the interface. The failures could be
         due to the following reasons: permission failure, bitrate
         failure, lack of resource or invalid group address.

         For MGMD version 2 it counts the number of Membership Report
         messages that failed to result in a successful join.

         MGMD version 3 defines a Membership Report message to contain
         multiple group records. Within a group record there is a
         parameter 'multicast address' and a list of 'source
         addresses'. A tree is managed per (multicast address, source
         address) pair. Hence a join is a request that requests
         associating the interface to a tree. In case one Membership
         Report message results in requests for associating the
         interface to N trees, then this corresponds to N joins. For
         MGMD version 3 the counter in-unsuccessful-join-requests
         counts the number of joins that did not result in
         successfully associating the interface to a tree.";
      reference
        "TR-101 - R-217, per DSL port, per multicast VLAN, item 2";
    }
    leaf in-leaves {
      type yang:counter32;
      description
        "For MGMD version 2 it counts the number of Leave Group
         messages received on this interface, i.e. messages that are
         requesting to leave a multicast group address.

         MGMD version 3 defines a Membership Report message to contain
         multiple group records. Within a group record there is a
         parameter 'multicast address' and a list of 'source
         addresses'. A tree is managed per (multicast address, source
         address) pair. Hence a leave is a request that requests to
         remove the association from an interface to a tree. In case
         one Membership Report message results in requests for
         removing N associations from the interface from trees, then
         this corresponds to N leaves.";
    }
    leaf in-valid-messages {
      type yang:counter32;
      description
        "For MGMD version 2 it counts the number of Membership Report
         messages plus the number of MGMD Leave Group messages
         received on this interface and that had valid formatting.

         For MGMD version 3 it also counts the number of Membership
         Report messages received on this interface and that had valid
         formatting.";
    }
    leaf in-invalid-messages {
      type yang:counter32;
      description
        "Counts the number of invalid MGMD messages received on this
         interface.";
      reference
        "TR-101 - R-217, per DSL port, per multicast VLAN, item 6";
    }
  }

  grouping mgmd-interface-to-hosts-transmit-state {
    description
      "Grouping of objects used for monitoring the Internet Group
       Management Protocol (IGMP) and the Multicast Listener Discovery
       (MLD) protocol on interfaces that connect a system to multicast
       hosts.";
    leaf out-specific-queries {
      type yang:counter32;
      description
        "For MGMD version 2 it counts the number of sent MGMD
         Group-Specific Query messages.

         MGMD version 3 defines a Query message to contain a single
         group address' and a list of 'source addresses'. A tree is
         managed per group address, source address) pair. For MGMD
         version 3 a MGMD Group-Specific Query message is a Query
         message for which the group address is not the zero address.
         The counter out-specific-queries is incremented once for a
         sent ASM Group-Specific Query message (i.e. no source
         address), and is incremented with N for SSM Group-Specific
         Query messages that are sent to the router, where N is the
         number of source addresses in the Query message.";
      reference
        "TR-101 - R-217, per DSL port, per multicast VLAN, item 5";
    }
    leaf out-general-queries {
      type yang:counter32;
      description
        "For MGMD version 2 it counts the number of sent MGMD General
         Query messages.

         MGMD version 3 defines a Query message to contain a single
         group address' and a list of 'source addresses'. For MGMD
         version 3 a MGMD General Query message is a Query message for
         which the group address is the zero address and there are no
         sources addresses. The counter out-generic-queries is
         incremented once per sent MGMD General Query message.";
      reference
        "TR-101 - R-217, per DSL port, per multicast VLAN, item 4";
    }
  }
}
