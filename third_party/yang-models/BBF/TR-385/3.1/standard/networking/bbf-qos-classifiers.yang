module bbf-qos-classifiers {
  yang-version 1.1;
  namespace "urn:bbf:yang:bbf-qos-classifiers";
  prefix bbf-qos-cls;

  import ietf-inet-types {
    prefix inet;
  }
  import bbf-yang-types {
    prefix bbf-yang;
  }
  import bbf-dot1q-types {
    prefix bbf-dot1qt;
  }
  import bbf-frame-classification {
    prefix bbf-classif;
  }
  import bbf-qos-types {
    prefix bbf-qos-t;
  }

  organization
    "Broadband Forum <https://www.broadband-forum.org>
     Common YANG Work Area";
  contact
    "Comments or questions about this Broadband Forum YANG module
     should be directed to <mailto:help@broadband-forum.org>.

     Editor:      Nick Hancock, ADTRAN

     Editor:      Ludwig Pauwels, Nokia

     PS Leader:   Joey Boyd, ADTRAN

     PS Leader:   Sowrirajan Padmanabhan, Nokia

     WA Director: Joey Boyd, ADTRAN

     WA Director: Sven Ooghe, Nokia";
  description
    "This module contains a collection of YANG definitions for
     supporting the Broadband Forum requirements on the management of
     Quality of Service (QoS) as applicable to access network
     equipment. As such, this module is specific to access network
     equipment (e.g., BBF-specified Access Nodes and FTTdp DPUs).

     Specifically, this module contains a collection of classifiers
     used by policies applied to packets.

     Copyright (c) 2017-2020, Broadband Forum

     Redistribution and use in source and binary forms, with or
     without modification, are permitted provided that the following
     conditions are met:

     1. Redistributions of source code must retain the above copyright
        notice, this list of conditions and the following disclaimer.

     2. Redistributions in binary form must reproduce the above
        copyright notice, this list of conditions and the following
        disclaimer in the documentation and/or other materials
        provided with the distribution.

     3. Neither the name of the copyright holder nor the names of its
        contributors may be used to endorse or promote products
        derived from this software without specific prior written
        permission.

     THIS SOFTWARE IS PROVIDED BY THE COPYRIGHT HOLDERS AND
     CONTRIBUTORS \"AS IS\" AND ANY EXPRESS OR IMPLIED WARRANTIES,
     INCLUDING, BUT NOT LIMITED TO, THE IMPLIED WARRANTIES OF
     MERCHANTABILITY AND FITNESS FOR A PARTICULAR PURPOSE ARE
     DISCLAIMED. IN NO EVENT SHALL THE COPYRIGHT HOLDER OR
     CONTRIBUTORS BE LIABLE FOR ANY DIRECT, INDIRECT, INCIDENTAL,
     SPECIAL, EXEMPLARY, OR CONSEQUENTIAL DAMAGES (INCLUDING, BUT
     NOT LIMITED TO, PROCUREMENT OF SUBSTITUTE GOODS OR SERVICES;
     LOSS OF USE, DATA, OR PROFITS; OR BUSINESS INTERRUPTION) HOWEVER
     CAUSED AND ON ANY THEORY OF LIABILITY, WHETHER IN CONTRACT,
     STRICT LIABILITY, OR TORT (INCLUDING NEGLIGENCE OR OTHERWISE)
     ARISING IN ANY WAY OUT OF THE USE OF THIS SOFTWARE, EVEN IF
     ADVISED OF THE POSSIBILITY OF SUCH DAMAGE.

     The above license is used as a license under copyright only.
     Please reference the Forum IPR Policy for patent licensing terms
     <https://www.broadband-forum.org/ipr-policy>.

     Any moral rights which are necessary to exercise under the above
     license grant are also deemed granted under this license.

     This version of this YANG module is part of TR-383a3; see
     the TR itself for full legal notices.";

  revision 2020-05-11 {
    description
      "Amendment 3 Straw Ballot
       * Approval Date:    TBD.
       * Publication Date: TBD.";
    reference
      "TR-383a3: Common YANG Modules
                 <https://www.broadband-forum.org/technical/download/
                          TR-383_Amendment-3.pdf>";
  }
  revision 2018-07-13 {
    description
      "Amendment 1.
       * Approval Date:    2018-06-04.
       * Publication Date: see revision date above.";
    reference
      "TR-383: Common YANG Modules
               <https://www.broadband-forum.org/technical/download/
                        TR-383_Amendment-1.pdf>";
  }
  revision 2017-05-08 {
    description
      "Initial revision.
       * Approval Date:    see revision date above.
       * Publication Date: 2017-06-02.";
    reference
      "TR-383: Common YANG Modules
               <https://www.broadband-forum.org/technical/download/
                        TR-383.pdf>";
  }

  feature qos-action-permit {
    description
      "This feature indicates whether the system supports the action
       'permit' for packets that are classified using a QoS
       classification mechanism.";
  }

  feature qos-configurable-system-defaults {
    description
      "This feature indicates whether the configuration of system
       defaults is supported.";
  }

  typedef qos-pbit-marking-index {
    type uint8;
    description
      "An index in a Priority Code Point bits (P-bit) marking list,
       generated via a QoS profile.";
  }

  typedef qos-dei-marking-index {
    type uint8;
    description
      "An index in a Drop Eligibility Inidicator (DEI) marking list
       generated via a QoS profile.";
  }

  identity classifier-entry-filter-operation-type {
    description
      "Classifier entry filter logical operation.";
  }

  identity match-any-filter {
    base classifier-entry-filter-operation-type;
    description
      "Classifier entry filter logical OR operation.";
  }

  identity match-all-filter {
    base classifier-entry-filter-operation-type;
    description
      "Classifier entry filter logical AND operation.";
  }

  identity action-type {
    description
      "This base identity type defines action-types.";
  }

  identity pbit-marking {
    base action-type;
    description
      "The action-type identity indicating the system shall generate
       one or more values for the priority bit (P-bit) bits.";
  }

  identity dei-marking {
    base action-type;
    description
      "The action-type identity indicating the system shall generate
       one or more values for the Drop Eligibility Inidicator (DEI)
       bit.";
  }

  identity scheduling-traffic-class {
    base action-type;
    description
      "The action-type identity indicating a scheduling traffic
       class.";
  }

  identity dscp-marking {
    base action-type;
    description
      "The action-type identity indicating the system shall generate
       a value for the Differentiated Services Code Point (DSCP)
       bits.";
  }

  identity permit {
    base action-type;
    description
      "The action-type identity indicating the permit action. I.e.
       packets to which this action is assigned are permitted and will
       be subject to thenext step of packet processing where further
       actions can be assigned.";
  }

  identity action-scope {
    description
      "This base identity type defines action scopes.";
  }

  identity vlan-sub-interface {
    base action-scope;
    description
      "The scope of the action is the VLAN sub-interface.";
  }

  identity ethernet-interface {
    base action-scope;
    description
      "The scope of the action is the Ethernet like interface.
       This encompasses all VLAN sub-interfaces within the
       Ethernet like interface in scope.";
  }

  typedef action-scope {
    type identityref {
      base action-scope;
    }
    description
      "The scope of the action.";
  }

  typedef qos-color {
    type enumeration {
      enum green {
        description
          "Identifies the green color packet.";
      }
      enum yellow {
        description
          "Identifies the yellow color packet.";
      }
      enum red {
        description
          "Identifies the red color packet.";
      }
    }
    description
      "Defines the packet color that match.";
  }

  grouping pbit-marking-list {
    description
      "Nodes used to define a list of p-bit metadata.";
    list pbit-marking-list {
      key "index";
      description
        "Creates metadata which can be used to determine
         p-bit values to write to a VLAN tag or as match
         criteria for another classifier associated with the
         same QoS policy. Each entry uses a unique numeric
         index associated with a p-bit value.";
      leaf index {
        type qos-pbit-marking-index;
        description
          "The index associated with a p-bit value.";
      }
      leaf pbit-value {
        type bbf-dot1qt:pbit;
        description
          "A p-bit value to be inserted in the p-bits of a
           packet's VLAN tag or as match criteria for another
           classifier associated with the same QoS policy.";
      }
    }
  }

  grouping dei-marking-list {
    description
      "Nodes used to define a list of DEI metadata.";
    list dei-marking-list {
      key "index";
      description
        "Creates metadata which can be used to determine
         DEI values to write to a VLAN tag or as match
         criteria for another classifier associated with the
         same QoS policy. Each entry uses a unique numeric
         index associated with a DEI value.";
      leaf index {
        type qos-dei-marking-index;
        description
          "The index associated with a DEI value.";
      }
      leaf dei-value {
        type bbf-dot1qt:dei;
        description
          "A DEI value to be inserted in the DEI bit of a
           packet's VLAN tag or as match criteria for another
           classifier associated with the same QoS policy.";
      }
    }
  }

  grouping dscp-marking {
    leaf dscp {
      type inet:dscp;
      description
        "The value to be inserted in the DSCP field in the header of
         an IP packet.";
    }
    description
      "DSCP marking grouping.";
  }

  grouping classifier-entry-inline-attr {
    description
      "Classifier inline attributes.";
    container match-criteria {
      status deprecated;
      description
        "Filter operations are performed on all match criteria with
         each having a default configuration.

         The 'match-all-filter' operation will logically AND each
         of the criteria. For example, configuring 'match-all' and
         dscp-range to 'any' will match on tagged and untagged packets
         that contain a DSCP field and contain any protocol as the
         default configuration for the protocol is 'any-protocol'.

         The 'match-any-filter' operation will logically OR each
         of the configured criteria. For example, configuring
         'untagged' and dscp-range to '10-20' will match on all
         untagged packets as well as any packet containing a DSCP
         value of 10 to 20 as well as packets containing any protocol
         as the default configuration for the protocol is
         'any-protocol'.";
      choice vlan-tag-match-type {
        default "match-all";
        status deprecated;
        description
          "Provides a choice of how the frames may be matched.";
        case match-all {
          status deprecated;
          leaf match-all {
            type empty;
            status deprecated;
            description
              "Matches all traffic, i.e; irrespective of the frame
               being tagged or untagged.";
          }
        }
        case untagged {
          status deprecated;
          leaf untagged {
            type empty;
            status deprecated;
            description
              "Untagged match. Matches all untagged traffic.";
          }
        }
        case vlan-tagged {
          status deprecated;
          list tag {
            key "index";
            min-elements 1;
            max-elements 2;
            status deprecated;
            description
              "The tags to match, with the outermost tag to match
               assigned index 0.";
            leaf index {
              type bbf-classif:tag-index;
              must 'count(../../tag[index = 0]) > 0' {
                error-message
                  "An inner tag can only be matched on when also
                   matching on an outer tag.";
                description
                  "Only allow matching on an inner tag, if also
                   matching on the outer tags at the same time.";
              }
              status deprecated;
              description
                "The index into the tag stack, outermost tag first.";
            }
            leaf in-pbit-list {
              type bbf-dot1qt:pbit-list;
              status deprecated;
              description
                "Filter containing P-bit value(s) to be matched with
                 the value of the corresponding packet field. The list
                 of values form an OR condition: in case the value of
                 the packet field matches with one of the values of
                 the leaf then there is a match. In case the leaf
                 specifies a set of values and none of them appear in
                 the packet, then there is no match. In case the leaf
                 specifies a value for a packet field that is not
                 present, then no packets match the filter. For
                 example, an untagged packet does not contain P-bits,
                 hence this packet will not match a specified P-bit
                 value. In case the leaf is an empty list, or unknown,
                 then no match is required and all packets classify
                 the filter, including untagged packets.

                 An Ethernet frame can contain multiple VLAN tags or
                 no VLAN tag. The vlan-tag-match-type/vlan-tagged/tag
                 is a list and the element with index 0 is used to
                 match with the P-bits of outermost VLAN tag of the
                 packet, the element with index 1 is used to match
                 with the P-bits of the second VLAN tag of the
                 packet.";
            }
            leaf in-dei {
              type uint8 {
                range "0..1";
              }
              status deprecated;
              description
                "Filter containing DEI bit value(s) to be matched with
                 the values of the corresponding packet fields. In
                 case the leaf
                 specifies a value for a packet field that is not
                 present, then no packets match the filter. For
                 example, an untagged packet does not contain a DEI
                 bit, hence this packet will not match a specified DEI
                 bit value. In case the leaf is unknown, no match is
                 required and all packets classify the filter,
                 including untagged packets.

                 An Ethernet frame can contain multiple VLAN tags or
                 no VLAN tag. The vlan-tag-match-type/vlan-tagged/tag
                 is a list and the element with index 0 is used to
                 match with the DEI bit of the outermost VLAN tag of
                 the packet, the element with index 1 is used to match
                 with the DEI bit of the second VLAN tag of the
                 packet.";
            }
          }
        }
      }
      leaf dscp-range {
        type bbf-classif:dscp-range-or-any;
        default "any";
        status deprecated;
        description
          "String identifying the DSCP values and/or range.";
      }
      choice protocols {
        default "any-protocol";
        status deprecated;
        description
          "The choice allows to specify combintations of packet field
           values that identify a particular protocol/ or allows to
           indicate any protocol.";
        case any-protocol {
          status deprecated;
          leaf any-protocol {
            type empty;
            status deprecated;
            description
              "Identifies any protocol, i.e. not match is specified
               for any protocol.";
          }
        }
        case protocol {
          status deprecated;
          leaf-list protocol {
            type bbf-classif:protocols;
            status deprecated;
            description
              "Defines the protocols which will be matched.";
          }
        }
      }
    }
  }

  grouping classifier-action-entry-cfg {
    description
      "List of actions to be applied to a classified set of packets.";
    list classifier-action-entry-cfg {
      key "action-type";
      ordered-by user;
      description
        "Configuration of classifier associated actions.";
      leaf action-type {
        type identityref {
          base action-type;
        }
        description
          "This defines the action type.";
      }
      choice action-cfg-params {
        description
          "Choice of action types.";
        case pbit-marking {
          container pbit-marking-cfg {
            when "../action-type='bbf-qos-cls:pbit-marking'" {
              description
                "Only applicable when the action-type is
                 pbit-marking.";
            }
            description
              "P-bit marking configuration container.";
            uses pbit-marking-list;
          }
        }
        case dei-marking {
          container dei-marking-cfg {
            when "../action-type='bbf-qos-cls:dei-marking'" {
              description
                "Only applicable when the action-type is
                 dei-marking.";
            }
            description
              "DEI marking configuration container.";
            uses dei-marking-list;
          }
        }
        case dscp-marking {
          container dscp-marking-cfg {
            when "../action-type='bbf-qos-cls:dscp-marking'" {
              description
                "Only applicable when the action-type is
                 dscp-marking.";
            }
            uses dscp-marking;
            description
              "DSCP marking configuration container.";
          }
        }
        case scheduling-traffic-class {
          leaf scheduling-traffic-class {
            when "../action-type=
                  'bbf-qos-cls:scheduling-traffic-class'" {
                description
                  "Only applicable when the action-type is
                   scheduling-traffic-class.";
            }
            type bbf-qos-t:traffic-class-id;
            description
              "Define the traffic class for scheduling.";
          }
        }
        case permit {
          if-feature "bbf-qos-cls:qos-action-permit";
          description
            "The action types for packets matching a classification
             criterium is that they are permitted and will be subject
             to further processing.";
          leaf permit {
            when '../bbf-qos-cls:action-type="bbf-qos-cls:permit"' {
              description
                "Only applicable when the action-type is 'permit'.";
            }
            type empty;
            description
              "The action types for packets matching a classification
               criterium is 'permit'.";
          }
        }
      }
    }
  }

  container classifiers {
    description
      "Provides data nodes that allow to configure methods to classify
       frames and assign actions in the context of QoS.";
    container system-default-actions {
      if-feature "qos-configurable-system-defaults";
      description
        "This container defines a set of data nodes that allow to
         configure the system default behjavior for when the
         processing of a packet requires data, and the former applying
         of QoS policiesk did not generate such data.

         More in detail, when a packet is received or to be
         transmitted on an interface, then it can be subject to
         QoS policies that are configured for this interface. The
         definition of QoS policies includes the assignment of
         'meta-data' to packets which can then be used during the
         further processing of the packet.

         An example is the assignment of a traffic class. This traffic
         class is used, after the forwarding decision has been made
         and all QOS polices are applied, to identify the queue on the
         outgoing interface. But what shall happen with the packet
         when it did not get a TC assigned, and one is needed? This is
         answered through the scheduling-traffic-class defined in this
         container.

         And similar for the other data nodes.";
      leaf scheduling-traffic-class {
        type union {
          type bbf-qos-t:traffic-class-id;
          type enumeration {
            enum discard {
              description
                "The traffic class 'discard' means that packets will
                 not get a traffic class by default. When the
                 processing of the packet comes to a moment that a
                 traffic class is needed, and none is assigned through
                 having applied the QoS profiles, then the system
                 shall discard the packet.";
            }
          }
        }
        description
          "Defines the traffic class assigned by default to packets.";
      }
      leaf flow-color {
        type union {
          type qos-color;
          type enumeration {
            enum discard {
              description
                "The flow color 'discard' means that packets will not
                 get a flow color by default. When the processing of
                 the packet comes to a moment that a flow color is
                 needed, and none is assigned through having applied
                 the QoS profiles, then the system shall discard the
                 packet.";
            }
          }
        }
        description
          "Defines the packet's flow color for when color-aware
           classification and/or actions are needed in the processing
           of a packet.";
      }
      leaf bac-color {
        type union {
          type qos-color;
          type enumeration {
            enum discard {
              description
                "The BAC color 'discard' means that packets will not
                 get a BAC color by default. When the processing of
                 the packet comes to a moment that a BAC color is
                 needed, and none is assigned through having applied
                 the QoS profiles, then the system shall discard the
                 packet.";
            }
          }
        }
        description
          "Defines the packet's BAC color for when color-aware
           classification and/or actions are needed in the processing
           of a packet. More specific, when the packet is to be queued
           using a color aware BAC method.";
      }
    }
    list classifier-entry {
      key "name";
      description
        "Classifier entry template.";
      leaf name {
        type bbf-yang:string-ascii64;
        description
          "Classifier name.";
      }
      leaf description {
        type bbf-yang:string-ascii64-or-empty;
        description
          "Description of the class template.";
      }
      leaf filter-operation {
        type identityref {
          base classifier-entry-filter-operation-type;
        }
        default "bbf-qos-cls:match-any-filter";
        status deprecated;
        description
          "Filters are applicable as any or all filters.";
      }
      choice filter-method {
        description
          "Choice of filter configuration way.";
        case inline {
          status deprecated;
          description
            "The classifier criteria are directly configured here.";
          uses classifier-entry-inline-attr {
            status deprecated;
          }
        }
        case all-packets {
          description
            "The classifier applies to all packets that are in the
             scope of the flow on which the classifier applies.";
          leaf all-packets {
            type empty;
            description
              "Identifies all packets.";
          }
        }
      }
      uses classifier-action-entry-cfg;
    }
  }

  grouping classifier-entry-ref {
    description
      "A reference to a classifier entry.";
    leaf name {
      type leafref {
        path "/bbf-qos-cls:classifiers/bbf-qos-cls:classifier-"
           + "entry/bbf-qos-cls:name";
      }
      description
        "The name of the referenced classifier entry.";
    }
  }

  grouping in-pbit-list {
    description
      "Ingress Priority Bits (P-bits) configuration.";
    leaf in-pbit-list {
      type bbf-dot1qt:pbit-list;
      description
        "Filter containing P-bit value(s) to be matched with the
         value of the corresponding packet field. The list of values
         form an OR condition: in case the value of the packet field
         matches with one of the values of the leaf then there is a
         match. In case the leaf specifies a set of values and none
         of them appear in the packet, then there is no match. In case
         the leaf specifies a value for a packet field that is not
         present, then no packets match the filter. E.g. an untagged
         packet does not contain P-bits, hence this packet will
         not match a specified P-bit value. In case the leaf is an
         empty list, or unknown, then no match is required and all
         packets classify the filter, including untagged packets.

         An Ethernet frame can contain multiple VLAN tags or no VLAN
         tag. The vlan-tag-match-type/vlan-tagged/tag is a list and
         the element with index 0 is used to match with the P-bits
         of outermost VLAN tag of the packet, the element with index
         1 is used to match with the P-bits of the second VLAN tag
         of the packet.";
    }
  }

  grouping in-dei {
    description
      "Ingress Drop Eligible Indicator (DEI) configuration.";
    leaf in-dei {
      type uint8 {
        range "0..1";
      }
      description
        "Filter containing DEI bit value(s) to be matched with the
         values of the corresponding packet fields. In case the leaf
         specifies a value for a packet field that is not present,
         then no packets match the filter. E.g. an untagged packet
         does not contain a DEI bit, hence this packet will not match
         a specified DEI bit value. In case the leaf is unknown,
         no match is required and all packets classify the filter,
         including untagged packets.

         An Ethernet frame can contain multiple VLAN tags or no VLAN
         tag. The vlan-tag-match-type/vlan-tagged/tag is a list and
         the element with index 0 is used to match with the DEI bit of
         the outermost VLAN tag of the packet, the element with index
         1 is used to match with the DEI bit of the second VLAN tag of
         the packet.";
    }
  }
}
