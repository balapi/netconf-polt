module bbf-qos-classifiers-state {
  yang-version 1.1;
  namespace "urn:bbf:yang:bbf-qos-classifiers-state";
  prefix bbf-qos-cls-state;

  import bbf-qos-classifiers {
    prefix bbf-qos-cls;
  }
  import bbf-qos-types {
    prefix bbf-qos-t;
  }

  organization
    "Broadband Forum <https://www.broadband-forum.org>
     Common YANG Work Area";
  contact
    "Comments or questions about this Broadband Forum YANG module
     should be directed to <mailto:help@broadband-forum.org>.

     Editor:      Nick Hancock, ADTRAN

     Editor:      Ludwig Pauwels, Nokia

     PS Leader:   Joey Boyd, ADTRAN

     PS Leader:   Sowrirajan Padmanabhan, Nokia

     WA Director: Joey Boyd, ADTRAN

     WA Director: Sven Ooghe, Nokia";
  description
    "This module contains a collection of YANG definitions for
     supporting the Broadband Forum requirements on the management of
     Quality of Service (QoS) as applicable to access network
     equipment. As such, this module is specific to access network
     equipment (e.g., BBF-specified Access Nodes and FTTdp DPUs).

     Specifically, this module contains a collection of classifiers
     used by policies applied to packets.

     Copyright (c) 2017-2020, Broadband Forum

     Redistribution and use in source and binary forms, with or
     without modification, are permitted provided that the following
     conditions are met:

     1. Redistributions of source code must retain the above copyright
        notice, this list of conditions and the following disclaimer.

     2. Redistributions in binary form must reproduce the above
        copyright notice, this list of conditions and the following
        disclaimer in the documentation and/or other materials
        provided with the distribution.

     3. Neither the name of the copyright holder nor the names of its
        contributors may be used to endorse or promote products
        derived from this software without specific prior written
        permission.

     THIS SOFTWARE IS PROVIDED BY THE COPYRIGHT HOLDERS AND
     CONTRIBUTORS \"AS IS\" AND ANY EXPRESS OR IMPLIED WARRANTIES,
     INCLUDING, BUT NOT LIMITED TO, THE IMPLIED WARRANTIES OF
     MERCHANTABILITY AND FITNESS FOR A PARTICULAR PURPOSE ARE
     DISCLAIMED. IN NO EVENT SHALL THE COPYRIGHT HOLDER OR
     CONTRIBUTORS BE LIABLE FOR ANY DIRECT, INDIRECT, INCIDENTAL,
     SPECIAL, EXEMPLARY, OR CONSEQUENTIAL DAMAGES (INCLUDING, BUT
     NOT LIMITED TO, PROCUREMENT OF SUBSTITUTE GOODS OR SERVICES;
     LOSS OF USE, DATA, OR PROFITS; OR BUSINESS INTERRUPTION) HOWEVER
     CAUSED AND ON ANY THEORY OF LIABILITY, WHETHER IN CONTRACT,
     STRICT LIABILITY, OR TORT (INCLUDING NEGLIGENCE OR OTHERWISE)
     ARISING IN ANY WAY OUT OF THE USE OF THIS SOFTWARE, EVEN IF
     ADVISED OF THE POSSIBILITY OF SUCH DAMAGE.

     The above license is used as a license under copyright only.
     Please reference the Forum IPR Policy for patent licensing terms
     <https://www.broadband-forum.org/ipr-policy>.

     Any moral rights which are necessary to exercise under the above
     license grant are also deemed granted under this license.

     This version of this YANG module is part of TR-383a3; see
     the TR itself for full legal notices.";

  revision 2020-05-11 {
    description
      "Amendment 3 Straw Ballot
       * Approval Date:    TBD.
       * Publication Date: TBD.";
    reference
      "TR-383a3: Common YANG Modules
                 <https://www.broadband-forum.org/technical/download/
                          TR-383_Amendment-3.pdf>";
  }

  container classifiers {
    config false;
    description
      "Provides data nodes that allow to report on system default
       methods for classifying frames and assigning actions in the
       context of QoS.";
    container system-default-actions {
      description
        "This container defines a set of system defaults for when the
         processing of a packet requires data, and the former applying
         of QoS policies did not generate such data.

         More in detail, when a packet is received or to be
         transmitted on an interface, then it can be subject to
         QoS policies that are configured for this interface. The
         definition of QoS policies includes the assignment of
         'meta-data' to packets which can then be used during the
         further processing of the packet.

         An example is the assignment of a traffic class. This traffic
         class is used, after the forwarding decision has been made
         and all QOS polices are applied, to identify the queue on the
         outgoing interface. But what shall happen with the packet
         when it did not get a TC assigned, and one is needed? This is
         answered through the scheduling-traffic-class defined in this
         container.

         And similar for the other data nodes.";
      leaf scheduling-traffic-class {
        type union {
          type bbf-qos-t:traffic-class-id;
          type enumeration {
            enum discard {
              description
                "The traffic class 'discard' means that packets will
                 not get a traffic class by default. When the
                 processing of the packet comes to a moment that a
                 traffic class is needed, and none is assigned through
                 having applied the QoS profiles, then the system
                 shall discard the packet.";
            }
          }
        }
        description
          "Defines the traffic class assigned by default to packets.";
      }
      leaf flow-color {
        type union {
          type bbf-qos-cls:qos-color;
          type enumeration {
            enum discard {
              description
                "The flow color 'discard' means that packets will not
                 get a flow color by default. When the processing of
                 the packet comes to a moment that a flow color is
                 needed, and none is assigned through having applied
                 the QoS profiles, then the system shall discard the
                 packet.";
            }
          }
        }
        description
          "Defines the packet's flow color for when color-aware
           classification and/or actions are needed in the processing
           of a packet.";
      }
      leaf bac-color {
        type union {
          type bbf-qos-cls:qos-color;
          type enumeration {
            enum discard {
              description
                "The BAC color 'discard' means that packets will not
                 get a BAC color by default. When the processing of
                 the packet comes to a moment that a BAC color is
                 needed, and none is assigned through having applied
                 the QoS profiles, then the system shall discard the
                 packet.";
            }
          }
        }
        description
          "Defines the packet's BAC color for when color-aware
           classification and/or actions are needed in the processing
           of a packet. More specific, when the packet is to be queued
           using a color aware BAC method.";
      }
    }
  }
}
