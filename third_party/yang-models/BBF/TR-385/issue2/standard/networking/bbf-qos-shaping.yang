module bbf-qos-shaping {
  yang-version 1.1;
  namespace "urn:bbf:yang:bbf-qos-shaping";
  prefix bbf-qos-shap;

  import bbf-yang-types {
    prefix bbf-yang;
  }
  import ietf-interfaces {
    prefix if;
  }
  import bbf-qos-traffic-mngt {
    prefix bbf-qos-tm;
  }

  organization
    "Broadband Forum <https://www.broadband-forum.org>
     Common YANG Work Area";
  contact
    "Comments or questions about this Broadband Forum YANG module
     should be directed to <mailto:help@broadband-forum.org>.

     Editor:      Nick Hancock, ADTRAN

     Editor:      Ludwig Pauwels, Nokia

     PS Leader:   Joey Boyd, ADTRAN

     PS Leader:   Sowrirajan Padmanabhan, Nokia

     WA Director: Joey Boyd, ADTRAN

     WA Director: Sven Ooghe, Nokia";
  description
    "This module contains a collection of YANG definitions for
     supporting the Broadband Forum requirements on the management of
     Quality of Service (QoS) as applicable to access network
     equipment. As such, this module is specific to access network
     equipment (e.g., BBF-specified Access Nodes and FTTdp DPUs).

     Specifically, this module contains shaping configuration data.

     Copyright (c) 2017-2020, Broadband Forum

     Redistribution and use in source and binary forms, with or
     without modification, are permitted provided that the following
     conditions are met:

     1. Redistributions of source code must retain the above copyright
        notice, this list of conditions and the following disclaimer.

     2. Redistributions in binary form must reproduce the above
        copyright notice, this list of conditions and the following
        disclaimer in the documentation and/or other materials
        provided with the distribution.

     3. Neither the name of the copyright holder nor the names of its
        contributors may be used to endorse or promote products
        derived from this software without specific prior written
        permission.

     THIS SOFTWARE IS PROVIDED BY THE COPYRIGHT HOLDERS AND
     CONTRIBUTORS \"AS IS\" AND ANY EXPRESS OR IMPLIED WARRANTIES,
     INCLUDING, BUT NOT LIMITED TO, THE IMPLIED WARRANTIES OF
     MERCHANTABILITY AND FITNESS FOR A PARTICULAR PURPOSE ARE
     DISCLAIMED. IN NO EVENT SHALL THE COPYRIGHT HOLDER OR
     CONTRIBUTORS BE LIABLE FOR ANY DIRECT, INDIRECT, INCIDENTAL,
     SPECIAL, EXEMPLARY, OR CONSEQUENTIAL DAMAGES (INCLUDING, BUT
     NOT LIMITED TO, PROCUREMENT OF SUBSTITUTE GOODS OR SERVICES;
     LOSS OF USE, DATA, OR PROFITS; OR BUSINESS INTERRUPTION) HOWEVER
     CAUSED AND ON ANY THEORY OF LIABILITY, WHETHER IN CONTRACT,
     STRICT LIABILITY, OR TORT (INCLUDING NEGLIGENCE OR OTHERWISE)
     ARISING IN ANY WAY OUT OF THE USE OF THIS SOFTWARE, EVEN IF
     ADVISED OF THE POSSIBILITY OF SUCH DAMAGE.

     The above license is used as a license under copyright only.
     Please reference the Forum IPR Policy for patent licensing terms
     <https://www.broadband-forum.org/ipr-policy>.

     Any moral rights which are necessary to exercise under the above
     license grant are also deemed granted under this license.

     This version of this YANG module is part of TR-383a3; see
     the TR itself for full legal notices.";

  revision 2020-05-11 {
    description
      "Amendment 3 Straw Ballot
       * Approval Date:    TBD.
       * Publication Date: TBD.";
    reference
      "TR-383a3: Common YANG Modules
                 <https://www.broadband-forum.org/technical/download/
                          TR-383_Amendment-3.pdf>";
  }
  revision 2018-07-13 {
    description
      "Amendment 1.
       * Approval Date:    2018-06-04.
       * Publication Date: see revision date above.";
    reference
      "TR-383: Common YANG Modules
               <https://www.broadband-forum.org/technical/download/
                        TR-383_Amendment-1.pdf>";
  }

  feature two-token-bucket-shaper {
    description
      "Indicates support for a two token bucket (dual rate) shaper.";
  }

  augment "/bbf-qos-tm:tm-profiles" {
    description
      "Augment the traffic management profile to add shaper
       configuration.";
    list shaper-profile {
      key "name";
      description
        "A list of shaper profiles.";
      leaf name {
        type bbf-yang:string-ascii64;
        description
          "The name of a shaper profile.";
      }
      choice shaper-type {
        mandatory true;
        description
          "Choice of shaper types.";
        case single-token-bucket {
          description
            "Applicable when the shaper type is single token.";
          container single-token-bucket {
            description
              "Management objects associated with single token.";
            leaf pir {
              type uint32;
              units "kbits per second";
              description
                "The Peak Information Rate (PIR), in kilobits per
                 second.";
            }
            leaf pbs {
              type uint32;
              units "bytes";
              description
                "The Peak Burst Size (PBS), in bytes.";
            }
          }
        }
        case two-token-bucket {
          if-feature "two-token-bucket-shaper";
          container two-token-bucket {
            description
              "A shaper which shapes traffic up to a Peak Information
               Rate (PIR) which also enforces a separate traffic rate
               limit as specified by a Committed Information Rate
               (CIR).

               The rate of traffic which exceeds CIR but is less than
               or equal to PIR, is considered to be the Excess
               Information Rate (EIR) traffic.";
            leaf pir {
              type uint32;
              units "kbits per second";
              mandatory true;
              description
                "The Peak Information Rate (PIR), in kilobits per
                 second.";
            }
            leaf cir {
              type uint32;
              units "kbits per second";
              mandatory true;
              description
                "The Committed Information Rate (CIR), in kilobits per
                 second.";
            }
          }
        }
      }
    }
  }

  grouping shaper-profile-ref {
    description
      "A reference to a shaper profile.";
    leaf shaper-name {
      type leafref {
        path "/bbf-qos-tm:tm-profiles/bbf-qos-shap:shaper-profile/"
           + "bbf-qos-shap:name";
      }
      description
        "An absolute reference to a shaper profile.";
    }
  }

  augment "/if:interfaces/if:interface/bbf-qos-tm:tm-root" {
    description
      "Augments the traffic management root with a reference to a
       shaper profile.";
    uses shaper-profile-ref;
  }

  augment "/if:interfaces/if:interface/bbf-qos-tm:tm-root/bbf-qos-"
        + "tm:children-type/bbf-qos-tm:queues/bbf-qos-tm:queue/bbf-"
        + "qos-tm:queue-scheduling-cfg-type/bbf-qos-tm:inline" {
    description
      "Augments the queues defined within the traffic management root
       with a reference to a shaper profile.";
    uses shaper-profile-ref;
  }
}
